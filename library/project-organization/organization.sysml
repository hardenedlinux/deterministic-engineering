// SPDX-FileCopyrightText: 2026 hardenedlinux Linux Team and Contributors
//
// SPDX-License-Identifier: LGPL-2.1-or-later

package RepositoryOrganization {
 part def LibraryDefinitions;
 part def IndependentProfile;
 part def ProjectScenario;
 part def ApplicationReasoning;
 part def ReviewBoundary;
 part def DocumentOrganization;
 part def MethodContracts;
 part def ReceiptBoundary;
 part def ProjectEntry;
}
